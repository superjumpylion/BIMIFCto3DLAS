FME workspace 2_BIMIFCtoDBMS.fmw
Title: BIMIFC to DBMS
Description: BIMIFC to DBMS
This workspace is used to read IFC-file(s), coerce and validate the geometry, then write it to the DBMS.
Requirements
See the PostgreSQL dll to install the database.
Input
PostgreSQL_CONNECTION - Connection to the database
InputFolder - Folder which contains the to be validated IFC-file(s)
History: 18 - 9 - 2021,Marjan Broekhuizen,Uploaded to Git

Parameters:
- INPUTFOLDER =
- PostgreSQL_CONNECTION =

Readers:
- CSV2_1: CSV2 from $(INPUTFOLDER)\*.csv

Writers:
- XLSXW_1: XLSXW to $(INPUTFOLDER)\GeometryValidatorOutput.xlsx
- POSTGRES_1: POSTGRES to $(PostgreSQL_CONNECTION)
- POSTGRES_2: POSTGRES to $(PostgreSQL_CONNECTION)
- POSTGRES_3: POSTGRES to $(PostgreSQL_CONNECTION)
- POSTGRES_4: POSTGRES to $(PostgreSQL_CONNECTION)

Creator
    GEOMTYPE = Geometry Object
    NUM = 1
    CREATED -> FeatureReader [INITIATOR]
    CREATED -> FeatureReader_2 [INITIATOR]
    CREATED -> FeatureReader_3 [INITIATOR]
AttributeKeeper
    CREATE_BULK_MODE_FEATURES = NO
    KEEP_ATTRS = Description,fme_basename,fme_feature_type,GlobalId,InteriorOrExteriorSpace,LongName,Name
    -> AttributeManager
AttributeManager
    ATTR_TABLE:
      RENAME_SET_VALUE fme_basename > Basename
      RENAME_SET_VALUE fme_feature_type > Entity
    -> IfcSpace_Coercer [IfcSpace]
IfcSpace_Coercer
    KIND = fme_brep_solid
    IfcSpace_Coerced -> Affine_IFC [CoercedGeo]
GeometryFilter
    BREAK_AGG = No
    GEOM_PORT_NAMES = Null
    <UNFILTERED> -> AttributeExposer
AttributeExposer
    ATTR_LIST = Description,fme_feature_type,GlobalId,Name
    -> AttributeManager_2
AttributeManager_2
    ATTR_TABLE:
      RENAME_SET_VALUE fme_feature_type > Entity
      RENAME_SET_VALUE fme_basename > Basename
    -> IfcSpace_Coercer_2 [IfcSpace]
IfcSpace_Coercer_2
    KIND = fme_composite_surface
    IfcSpace_Coerced -> Affine_IFC_2 [CoercedGeo]
Affine_IFC
    MOVEX = @Value(MoveX)
    MOVEY = @Value(MoveY)
    MOZEZ = @Value(MozeZ)
    SCALE = @Value(Scale)
    3DAffined -> ValidateGeometry
ValidateGeometry
    BASENAME = @Value(Basename)
    ENTITY = @Value(Entity)
    GLOBALID = @Value(GlobalId)
    Valid_Geometries -> AttributeKeeper_2
    Report_Summary -> SpaceSummary (writer XLSXW_1)
    Report_Failed -> SpaceFailed (writer XLSXW_1)
    Report_FailedRepaired -> SpaceRepaired (writer XLSXW_1)
    Report_SummarizedIssues -> SpaceIssueSummary (writer XLSXW_1)
AttributeKeeper_2
    CREATE_BULK_MODE_FEATURES = NO
    KEEP_ATTRS = Basename,Description,Entity,GlobalId,InteriorOrExteriorSpace,LongName,Name
    -> FeatureWriter [Valid_Geometries]
Affine_IFC_2
    MOVEX = @Value(MoveX)
    MOVEY = @Value(MoveY)
    MOZEZ = @Value(MozeZ)
    SCALE = @Value(Scale)
    3DAffined -> ValidateGeometry_2
ValidateGeometry_2
    BASENAME = @Value(Basename)
    ENTITY = @Value(Entity)
    GLOBALID = @Value(GlobalId)
    Valid_Geometries -> AttributeKeeper_3
    Report_Summary -> BESummary (writer XLSXW_1)
    Report_Failed -> BESpaceFailed (writer XLSXW_1)
    Report_FailedRepaired -> BERepaired (writer XLSXW_1)
    Report_SummarizedIssues -> BESpaceIssueSummary (writer XLSXW_1)
AttributeKeeper_3
    CREATE_BULK_MODE_FEATURES = NO
    KEEP_ATTRS = Basename,Description,Entity,GlobalId,InteriorOrExteriorSpace,LongName,Name
    -> FeatureWriter_2 [Valid_Geometries]

Bookmark: IFC
Note: IFC SPACE
FeatureReader
    ATTRIBUTES = IfcBeam,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename,ifc_parent_id",IfcBuilding,"GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,fme_geometry{0},fme_geometry{1},fme_geometry{2},fme_geometry{3},fme_geometry{4},fme_geometry{5},fme_geometry{6},fme_geometry{7},fme_geometry{8},Axis,Body,Box,FootPrint,fme_feature_type,fme_basename,ifc_parent_id",IfcBuildingStorey,"GlobalId,Name,Description,ObjectType,LongName,CompositionType,Elevation,fme_geometry{0},fme_geometry{1},fme_geometry{2},fme_geometry{3},fme_geometry{4},fme_geometry{5},fme_geometry{6},fme_geometry{7},fme_geometry{8},Axis,Body,Box,FootPrint,fme_feature_type,fme_basename,ifc_parent_id",IfcColumn,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename,ifc_parent_id",IfcCovering,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_feature_type,fme_basename,ifc_parent_id",IfcCurtainWall,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename,ifc_parent_id",IfcDoor,"GlobalId,Name,Description,ObjectType,Tag,OverallHeight,OverallWidth,fme_geometry{0},fme_geometry{1},fme_geometry{2},fme_geometry{3},fme_geometry{4},fme_geometry{5},fme_geometry{6},fme_geometry{7},fme_geometry{8},Axis,Body,Box,FootPrint,fme_feature_type,fme_basename,ifc_parent_id",IfcFlowTerminal,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename,ifc_parent_id",IfcMember,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename,ifc_parent_id",IfcOpeningElement,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename,ifc_parent_id",IfcProject,"GlobalId,Name,Description,ObjectType,LongName,Phase,fme_geometry{0},fme_geometry{1},fme_geometry{2},fme_geometry{3},fme_geometry{4},fme_geometry{5},fme_geometry{6},fme_geometry{7},fme_geometry{8},Axis,Body,Box,FootPrint,fme_feature_type,fme_basename,ifc_parent_id",IfcRailing,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_feature_type,fme_basename,ifc_parent_id",IfcRoof,"GlobalId,Name,Description,ObjectType,Tag,ShapeType,fme_geometry{0},fme_geometry{1},fme_geometry{2},fme_geometry{3},fme_geometry{4},fme_geometry{5},fme_geometry{6},fme_geometry{7},fme_geometry{8},Axis,Body,Box,FootPrint,fme_feature_type,fme_basename,ifc_parent_id",IfcSite,"GlobalId,Name,Description,ObjectType,LongName,CompositionType,RefLatitude,RefLongitude,RefElevation,LandTitleNumber,SiteAddress.Purpose,SiteAddress.Description,SiteAddress.UserDefinedPurpose,SiteAddress.InternalLocation,SiteAddress.AddressLines,SiteAddress.PostalBox,SiteAddress.Town,SiteAddress.Region,SiteAddress.PostalCode,SiteAddress.Country,fme_geometry{0},fme_geometry{1},fme_geometry{2},fme_geometry{3},fme_geometry{4},fme_geometry{5},fme_geometry{6},fme_geometry{7},fme_geometry{8},Axis,Body,Box,FootPrint,fme_feature_type,fme_basename,ifc_parent_id",IfcSlab,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_feature_type,fme_basename,ifc_parent_id",IfcSpace,"GlobalId,Name,Description,ObjectType,LongName,CompositionType,InteriorOrExteriorSpace,ElevationWithFlooring,fme_geometry{0},fme_geometry{1},fme_geometry{2},fme_geometry{3},fme_geometry{4},fme_geometry{5},fme_geometry{6},fme_geometry{7},fme_geometry{8},Axis,Body,Box,FootPrint,fme_feature_type,fme_basename,ifc_parent_id",IfcStair,"GlobalId,Name,Description,ObjectType,Tag,ShapeType,fme_geometry{0},fme_geometry{1},fme_geometry{2},fme_geometry{3},fme_geometry{4},fme_geometry{5},fme_geometry{6},fme_geometry{7},fme_geometry{8},Axis,Body,Box,FootPrint,fme_feature_type,fme_basename,ifc_parent_id",IfcTypeObject,"ifc_type_name,ifc_unique_id,GlobalId,Name,Description,ApplicableOccurrence,Tag,ElementType,PredefinedType,fme_feature_type,fme_basename,ifc_parent_id",IfcWall,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename,ifc_parent_id",IfcWallStandardCase,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename,ifc_parent_id",IfcWindow,"GlobalId,Name,Description,ObjectType,Tag,OverallHeight,OverallWidth,fme_geometry{0},fme_geometry{1},fme_geometry{2},fme_geometry{3},fme_geometry{4},fme_geometry{5},fme_geometry{6},fme_geometry{7},fme_geometry{8},Axis,Body,Box,FootPrint,fme_feature_type,fme_basename,ifc_parent_id",PropertySetDefinition,"fme_feature_type,fme_basename,ifc_parent_id",QuantitySetDefinition,"fme_feature_type,fme_basename,ifc_parent_id"
    ATTR_ACCUM_MODE = Only Use Result
    COMBINE_GEOM = Use Result
    COORDSYS = EPSG:3857
    DATASET = $(INPUTFOLDER)\*.IFC
    FEATURETYPES = IfcSpace
    FORMAT = IFC
    IFC_ADD_PROJECTIONS = Yes
    IFC_CREATE_PQSET_DEFINITION_FEATURES = Yes
    IFC_EVALUATE_CSG_SOLIDS = No
    IFC_IFCSPACE_GEOMETRY = Yes
    IFC_IFC_EXPOSE_FORMAT_ATTRS = fme_feature_type,char(50) fme_basename,char(50) ifc_parent_id,string
    IFC_MERGE_TYPE_OBJECT_PQSETS = YES
    IFC_PQSET_READ_MODE = GEOMETRIES
    IFC_READER_MODE = Relational
    IFC_READER_VERSION = 2014
    IFC_READ_ALL_REPRESENTATIONS = YES
    IFC_SIMPLIFY_BASE_FACES = No
    IFC_SUBTRACT_OPENINGS = Yes
    IFC_TYPE_OBJECT_READ_MODE = MERGED
    IFC_USE_SEARCH_ENVELOPE = NO
    IFC_VERSION_OVERRIDE = auto-detect
    INTERACT = NONE
    OUTPUT_FEATURES_DISPLAY = Schema and Data Features
    IfcSpace -> AttributeKeeper
Note: IFC BUILDING ELEMENTS
FeatureReader_2
    ATTRIBUTES = IfcBeam,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename",IfcBuilding,"GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,fme_geometry{0},fme_geometry{1},fme_geometry{2},fme_geometry{3},fme_geometry{4},fme_geometry{5},fme_geometry{6},fme_geometry{7},fme_geometry{8},Axis,Body,Box,FootPrint,fme_feature_type,fme_basename",IfcBuildingStorey,"GlobalId,Name,Description,ObjectType,LongName,CompositionType,Elevation,fme_geometry{0},fme_geometry{1},fme_geometry{2},fme_geometry{3},fme_geometry{4},fme_geometry{5},fme_geometry{6},fme_geometry{7},fme_geometry{8},Axis,Body,Box,FootPrint,fme_feature_type,fme_basename",IfcColumn,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename",IfcCovering,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_feature_type,fme_basename",IfcCurtainWall,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename",IfcDoor,"GlobalId,Name,Description,ObjectType,Tag,OverallHeight,OverallWidth,fme_geometry{0},fme_geometry{1},fme_geometry{2},fme_geometry{3},fme_geometry{4},fme_geometry{5},fme_geometry{6},fme_geometry{7},fme_geometry{8},Axis,Body,Box,FootPrint,fme_feature_type,fme_basename",IfcFlowTerminal,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename",IfcMember,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename",IfcOpeningElement,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename",IfcProject,"GlobalId,Name,Description,ObjectType,LongName,Phase,fme_geometry{0},fme_geometry{1},fme_geometry{2},fme_geometry{3},fme_geometry{4},fme_geometry{5},fme_geometry{6},fme_geometry{7},fme_geometry{8},Axis,Body,Box,FootPrint,fme_feature_type,fme_basename",IfcRailing,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_feature_type,fme_basename",IfcRoof,"GlobalId,Name,Description,ObjectType,Tag,ShapeType,fme_geometry{0},fme_geometry{1},fme_geometry{2},fme_geometry{3},fme_geometry{4},fme_geometry{5},fme_geometry{6},fme_geometry{7},fme_geometry{8},Axis,Body,Box,FootPrint,fme_feature_type,fme_basename",IfcSite,"GlobalId,Name,Description,ObjectType,LongName,CompositionType,RefLatitude,RefLongitude,RefElevation,LandTitleNumber,SiteAddress.Purpose,SiteAddress.Description,SiteAddress.UserDefinedPurpose,SiteAddress.InternalLocation,SiteAddress.AddressLines,SiteAddress.PostalBox,SiteAddress.Town,SiteAddress.Region,SiteAddress.PostalCode,SiteAddress.Country,fme_geometry{0},fme_geometry{1},fme_geometry{2},fme_geometry{3},fme_geometry{4},fme_geometry{5},fme_geometry{6},fme_geometry{7},fme_geometry{8},Axis,Body,Box,FootPrint,fme_feature_type,fme_basename",IfcSlab,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_feature_type,fme_basename",IfcSpace,"GlobalId,Name,Description,ObjectType,LongName,CompositionType,InteriorOrExteriorSpace,ElevationWithFlooring,fme_geometry{0},fme_geometry{1},fme_geometry{2},fme_geometry{3},fme_geometry{4},fme_geometry{5},fme_geometry{6},fme_geometry{7},fme_geometry{8},Axis,Body,Box,FootPrint,fme_feature_type,fme_basename",IfcStair,"GlobalId,Name,Description,ObjectType,Tag,ShapeType,fme_geometry{0},fme_geometry{1},fme_geometry{2},fme_geometry{3},fme_geometry{4},fme_geometry{5},fme_geometry{6},fme_geometry{7},fme_geometry{8},Axis,Body,Box,FootPrint,fme_feature_type,fme_basename",IfcTypeObject,"ifc_type_name,ifc_unique_id,GlobalId,Name,Description,ApplicableOccurrence,Tag,ElementType,PredefinedType,fme_feature_type,fme_basename",IfcWall,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename",IfcWallStandardCase,"GlobalId,Name,Description,ObjectType,Tag,fme_geometry{0},fme_geometry{1},fme_geometry{2},fme_geometry{3},fme_geometry{4},fme_geometry{5},fme_geometry{6},fme_geometry{7},fme_geometry{8},Axis,Body,Box,FootPrint,fme_feature_type,fme_basename",IfcWindow,"GlobalId,Name,Description,ObjectType,Tag,OverallHeight,OverallWidth,fme_geometry{0},fme_geometry{1},fme_geometry{2},fme_geometry{3},fme_geometry{4},fme_geometry{5},fme_geometry{6},fme_geometry{7},fme_geometry{8},Axis,Body,Box,FootPrint,fme_feature_type,fme_basename",PropertySetDefinition,"fme_feature_type,fme_basename",QuantitySetDefinition,"fme_feature_type,fme_basename"
    ATTR_ACCUM_MODE = Only Use Result
    COMBINE_GEOM = Use Result
    COORDSYS = EPSG:3857
    DATASET = G:\Git\Persoonlijk\BIMIFCtoLAS\Data\Central Park\E_CP_BWK_GA_Central_Park.ifc
    FORMAT = IFC
    IFC_ADD_PROJECTIONS = Yes
    IFC_CREATE_PQSET_DEFINITION_FEATURES = Yes
    IFC_EVALUATE_CSG_SOLIDS = Yes
    IFC_IFCSPACE_GEOMETRY = No
    IFC_IFC_EXPOSE_FORMAT_ATTRS = fme_basename,char(50)
    IFC_MERGE_TYPE_OBJECT_PQSETS = YES
    IFC_PQSET_READ_MODE = GEOMETRIES
    IFC_READER_MODE = Relational
    IFC_READER_VERSION = 2014
    IFC_READ_ALL_REPRESENTATIONS = YES
    IFC_SIMPLIFY_BASE_FACES = Yes
    IFC_SUBTRACT_OPENINGS = Yes
    IFC_TYPE_OBJECT_READ_MODE = MERGED
    IFC_USE_SEARCH_ENVELOPE = NO
    IFC_VERSION_OVERRIDE = auto-detect
    INTERACT = NONE
    OUTPUT_FEATURES_DISPLAY = Schema and Data Features
    <OTHER> -> GeometryFilter
Note: IFC INFO
FeatureReader_3
    ATTRIBUTES = IfcBeam,"GlobalId,Name,Description,ObjectType,Tag,fme_geometry{0},fme_geometry{1},fme_geometry{2},fme_geometry{3},fme_geometry{4},fme_geometry{5},fme_geometry{6},fme_geometry{7},fme_geometry{8},Axis,Body,Box,FootPrint",IfcBuilding,"GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,fme_geometry{0},fme_geometry{1},fme_geometry{2},fme_geometry{3},fme_geometry{4},fme_geometry{5},fme_geometry{6},fme_geometry{7},fme_geometry{8},Axis,Body,Box,FootPrint",IfcBuildingStorey,"GlobalId,Name,Description,ObjectType,LongName,CompositionType,Elevation,fme_geometry{0},fme_geometry{1},fme_geometry{2},fme_geometry{3},fme_geometry{4},fme_geometry{5},fme_geometry{6},fme_geometry{7},fme_geometry{8},Axis,Body,Box,FootPrint",IfcColumn,"GlobalId,Name,Description,ObjectType,Tag,fme_geometry{0},fme_geometry{1},fme_geometry{2},fme_geometry{3},fme_geometry{4},fme_geometry{5},fme_geometry{6},fme_geometry{7},fme_geometry{8},Axis,Body,Box,FootPrint",IfcCovering,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint",IfcCurtainWall,"GlobalId,Name,Description,ObjectType,Tag,fme_geometry{0},fme_geometry{1},fme_geometry{2},fme_geometry{3},fme_geometry{4},fme_geometry{5},fme_geometry{6},fme_geometry{7},fme_geometry{8},Axis,Body,Box,FootPrint",IfcDoor,"GlobalId,Name,Description,ObjectType,Tag,OverallHeight,OverallWidth,fme_geometry{0},fme_geometry{1},fme_geometry{2},fme_geometry{3},fme_geometry{4},fme_geometry{5},fme_geometry{6},fme_geometry{7},fme_geometry{8},Axis,Body,Box,FootPrint",IfcFlowTerminal,"GlobalId,Name,Description,ObjectType,Tag,fme_geometry{0},fme_geometry{1},fme_geometry{2},fme_geometry{3},fme_geometry{4},fme_geometry{5},fme_geometry{6},fme_geometry{7},fme_geometry{8},Axis,Body,Box,FootPrint",IfcMember,"GlobalId,Name,Description,ObjectType,Tag,fme_geometry{0},fme_geometry{1},fme_geometry{2},fme_geometry{3},fme_geometry{4},fme_geometry{5},fme_geometry{6},fme_geometry{7},fme_geometry{8},Axis,Body,Box,FootPrint",IfcOpeningElement,"GlobalId,Name,Description,ObjectType,Tag,fme_geometry{0},fme_geometry{1},fme_geometry{2},fme_geometry{3},fme_geometry{4},fme_geometry{5},fme_geometry{6},fme_geometry{7},fme_geometry{8},Axis,Body,Box,FootPrint",IfcProject,"GlobalId,Name,Description,ObjectType,LongName,Phase,fme_geometry{0},fme_geometry{1},fme_geometry{2},fme_geometry{3},fme_geometry{4},fme_geometry{5},fme_geometry{6},fme_geometry{7},fme_geometry{8},Axis,Body,Box,FootPrint",IfcRailing,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint",IfcRoof,"GlobalId,Name,Description,ObjectType,Tag,ShapeType,fme_geometry{0},fme_geometry{1},fme_geometry{2},fme_geometry{3},fme_geometry{4},fme_geometry{5},fme_geometry{6},fme_geometry{7},fme_geometry{8},Axis,Body,Box,FootPrint",IfcSite,"GlobalId,Name,Description,ObjectType,LongName,CompositionType,RefLatitude,RefLongitude,RefElevation,LandTitleNumber,SiteAddress.Purpose,SiteAddress.Description,SiteAddress.UserDefinedPurpose,SiteAddress.InternalLocation,SiteAddress.AddressLines,SiteAddress.PostalBox,SiteAddress.Town,SiteAddress.Region,SiteAddress.PostalCode,SiteAddress.Country,fme_geometry{0},fme_geometry{1},fme_geometry{2},fme_geometry{3},fme_geometry{4},fme_geometry{5},fme_geometry{6},fme_geometry{7},fme_geometry{8},Axis,Body,Box,FootPrint",IfcSlab,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint",IfcSpace,"GlobalId,Name,Description,ObjectType,LongName,CompositionType,InteriorOrExteriorSpace,ElevationWithFlooring,fme_geometry{0},fme_geometry{1},fme_geometry{2},fme_geometry{3},fme_geometry{4},fme_geometry{5},fme_geometry{6},fme_geometry{7},fme_geometry{8},Axis,Body,Box,FootPrint",IfcStair,"GlobalId,Name,Description,ObjectType,Tag,ShapeType,fme_geometry{0},fme_geometry{1},fme_geometry{2},fme_geometry{3},fme_geometry{4},fme_geometry{5},fme_geometry{6},fme_geometry{7},fme_geometry{8},Axis,Body,Box,FootPrint",IfcTypeObject,"ifc_type_name,ifc_unique_id,GlobalId,Name,Description,ApplicableOccurrence,Tag,ElementType,PredefinedType",IfcWall,"GlobalId,Name,Description,ObjectType,Tag,fme_geometry{0},fme_geometry{1},fme_geometry{2},fme_geometry{3},fme_geometry{4},fme_geometry{5},fme_geometry{6},fme_geometry{7},fme_geometry{8},Axis,Body,Box,FootPrint",IfcWallStandardCase,"GlobalId,Name,Description,ObjectType,Tag,fme_geometry{0},fme_geometry{1},fme_geometry{2},fme_geometry{3},fme_geometry{4},fme_geometry{5},fme_geometry{6},fme_geometry{7},fme_geometry{8},Axis,Body,Box,FootPrint",IfcWindow,"GlobalId,Name,Description,ObjectType,Tag,OverallHeight,OverallWidth,fme_geometry{0},fme_geometry{1},fme_geometry{2},fme_geometry{3},fme_geometry{4},fme_geometry{5},fme_geometry{6},fme_geometry{7},fme_geometry{8},Axis,Body,Box,FootPrint",PropertySetDefinition,,QuantitySetDefinition,
    ATTR_ACCUM_MODE = Only Use Result
    COMBINE_GEOM = Use Result
    COORDSYS = EPSG:3857
    DATASET = $(INPUTFOLDER)\*.IFC
    FEATURETYPES = IfcBuilding IfcBuildingStorey IfcProject IfcSite
    FORMAT = IFC
    IFC_ADD_PROJECTIONS = Yes
    IFC_CREATE_PQSET_DEFINITION_FEATURES = Yes
    IFC_EVALUATE_CSG_SOLIDS = No
    IFC_IFCSPACE_GEOMETRY = No
    IFC_MERGE_TYPE_OBJECT_PQSETS = YES
    IFC_PQSET_READ_MODE = GEOMETRIES
    IFC_READER_MODE = Relational
    IFC_READER_VERSION = 2014
    IFC_READ_ALL_REPRESENTATIONS = YES
    IFC_SIMPLIFY_BASE_FACES = No
    IFC_SUBTRACT_OPENINGS = Yes
    IFC_TYPE_OBJECT_READ_MODE = MERGED
    IFC_USE_SEARCH_ENVELOPE = NO
    IFC_VERSION_OVERRIDE = auto-detect
    INTERACT = NONE
    OUTPUT_FEATURES_DISPLAY = Schema and Data Features
    IfcBuilding -> BulkAttributeRenamer_2
    IfcBuildingStorey -> BulkAttributeRenamer_3
    IfcProject -> BulkAttributeRenamer_4
    IfcSite -> BulkAttributeRenamer

Bookmark: Add Prefixes
Note: Prefix IfcProject
BulkAttributeRenamer_4
    ATTRCHOICE = All Attributes
    MODE_CHOICE = RENAME
    PATTERN_ACTION_DISP = ADDPREFIX
    REPLACE_STR = IfcProject_
    -> AttributeManager_6
Note: Prefix IfcSite_
BulkAttributeRenamer
    ATTRCHOICE = All Attributes
    MODE_CHOICE = RENAME
    PATTERN_ACTION_DISP = ADDPREFIX
    REPLACE_STR = IfcSite_
    -> AttributeManager_3
Note: Prefix IfcBuilding_
BulkAttributeRenamer_2
    ATTRCHOICE = All Attributes
    MODE_CHOICE = RENAME
    PATTERN_ACTION_DISP = ADDPREFIX
    REPLACE_STR = IfcBuilding_
    -> AttributeManager_4
Note: Prefix IfcBuildingStorey
BulkAttributeRenamer_3
    ATTRCHOICE = All Attributes
    MODE_CHOICE = RENAME
    PATTERN_ACTION_DISP = ADDPREFIX
    REPLACE_STR = IfcBuildingStorey_
    -> AttributeManager_5

Bookmark: Remove unneeded attributes
AttributeManager_6
    ATTR_TABLE:
      REMOVE IfcProject_Description
      REMOVE IfcProject_ObjectType
      REMOVE IfcProject_Tag
      REMOVE IfcProject_Axis
      REMOVE IfcProject_Body
      REMOVE IfcProject_Box
      REMOVE IfcProject_FootPrint
      REMOVE IfcProject_SiteAddress.PostalCode
      REMOVE IfcProject_LandTitleNumber
      REMOVE IfcProject_SiteAddress.Description
      REMOVE IfcProject_ifc_type_name
      REMOVE IfcProject_SiteAddress.Country
      REMOVE IfcProject_RefLongitude
      REMOVE IfcProject_SiteAddress.Purpose
      REMOVE IfcProject_RefElevation
      REMOVE IfcProject_SiteAddress.Region
      REMOVE IfcProject_BuildingAddress.Purpose
      REMOVE IfcProject_ShapeType
      REMOVE IfcProject_BuildingAddress.UserDefinedPurpose
      REMOVE IfcProject_SiteAddress.AddressLines
      REMOVE IfcProject_CompositionType
      REMOVE IfcProject_BuildingAddress.PostalCode
      REMOVE IfcProject_BuildingAddress.Country
      REMOVE IfcProject_RefLatitude
      REMOVE IfcProject_ElevationWithFlooring
      REMOVE IfcProject_BuildingAddress.Region
      REMOVE IfcProject_BuildingAddress.Description
      REMOVE IfcProject_ifc_unique_id
      REMOVE IfcProject_BuildingAddress.PostalBox
      REMOVE IfcProject_PredefinedType
      REMOVE IfcProject_ElevationOfRefHeight
      REMOVE IfcProject_BuildingAddress.AddressLines
      REMOVE IfcProject_Elevation
      REMOVE IfcProject_BuildingAddress.Town
      REMOVE IfcProject_SiteAddress.Town
      REMOVE IfcProject_OverallWidth
      REMOVE IfcProject_Phase
      REMOVE IfcProject_OverallHeight
      REMOVE IfcProject_SiteAddress.UserDefinedPurpose
      REMOVE IfcProject_ApplicableOccurrence
      REMOVE IfcProject_InteriorOrExteriorSpace
      REMOVE IfcProject_ElementType
      REMOVE IfcProject_ifc_type_object_id
      REMOVE IfcProject_ifc_parent_unique_id
      REMOVE IfcProject_ElevationOfTerrain
      REMOVE IfcProject_SiteAddress.InternalLocation
      REMOVE IfcProject_BuildingAddress.InternalLocation
      REMOVE IfcProject_SiteAddress.PostalBox
      REMOVE fme_feature_type
    -> IFC_Project (writer POSTGRES_1)
AttributeManager_3
    ATTR_TABLE:
      REMOVE IfcSite_ifc_type_object_id
      REMOVE IfcSite_ObjectType
      REMOVE IfcSite_Description
      REMOVE IfcSite_SiteAddress.AddressLines
      REMOVE IfcSite_ElementType
      REMOVE IfcSite_ifc_parent_unique_id
      REMOVE IfcSite_ifc_unique_id
      REMOVE IfcSite_Tag
      REMOVE IfcSite_Axis
      REMOVE IfcSite_Body
      REMOVE IfcSite_Box
      REMOVE IfcSite_FootPrint
      REMOVE IfcSite_SiteAddress.PostalCode
      REMOVE IfcSite_LandTitleNumber
      REMOVE IfcSite_SiteAddress.Description
      REMOVE IfcSite_ifc_type_name
      REMOVE IfcSite_SiteAddress.Country
      REMOVE IfcSite_SiteAddress.Purpose
      REMOVE IfcSite_SiteAddress.Region
      REMOVE IfcSite_BuildingAddress.Purpose
      REMOVE IfcSite_ShapeType
      REMOVE IfcSite_BuildingAddress.UserDefinedPurpose
      REMOVE IfcSite_CompositionType
      REMOVE IfcSite_BuildingAddress.PostalCode
      REMOVE IfcSite_BuildingAddress.Country
      REMOVE IfcSite_ElevationWithFlooring
      REMOVE IfcSite_BuildingAddress.Region
      REMOVE IfcSite_BuildingAddress.Description
      REMOVE IfcSite_BuildingAddress.PostalBox
      REMOVE IfcSite_PredefinedType
      REMOVE IfcSite_ElevationOfRefHeight
      REMOVE IfcSite_BuildingAddress.AddressLines
      REMOVE IfcSite_Elevation
      REMOVE IfcSite_BuildingAddress.Town
      REMOVE IfcSite_SiteAddress.Town
      REMOVE IfcSite_OverallWidth
      REMOVE IfcSite_Phase
      REMOVE IfcSite_OverallHeight
      REMOVE IfcSite_SiteAddress.UserDefinedPurpose
      REMOVE IfcSite_ApplicableOccurrence
      REMOVE IfcSite_InteriorOrExteriorSpace
      REMOVE IfcSite_ElevationOfTerrain
      REMOVE IfcSite_SiteAddress.InternalLocation
      REMOVE IfcSite_BuildingAddress.InternalLocation
      REMOVE IfcSite_SiteAddress.PostalBox
      REMOVE fme_feature_type
    -> IFC_Site (writer POSTGRES_2)
AttributeManager_4
    ATTR_TABLE:
      REMOVE IfcBuilding_ElevationWithFlooring
      REMOVE IfcBuilding_ifc_parent_unique_id
      REMOVE IfcBuilding_ifc_unique_id
      REMOVE IfcBuilding_Description
      REMOVE IfcBuilding_ObjectType
      REMOVE IfcBuilding_Body
      REMOVE IfcBuilding_BuildingAddress.Country
      REMOVE IfcBuilding_BuildingAddress.Region
      REMOVE IfcBuilding_BuildingAddress.Description
      REMOVE IfcBuilding_BuildingAddress.InternalLocation
      REMOVE IfcBuilding_RefLatitude
      REMOVE IfcBuilding_RefLongitude
      REMOVE IfcBuilding_Tag
      REMOVE IfcBuilding_SiteAddress.Description
      REMOVE IfcBuilding_SiteAddress.PostalCode
      REMOVE IfcBuilding_Axis
      REMOVE IfcBuilding_Box
      REMOVE IfcBuilding_FootPrint
      REMOVE IfcBuilding_LandTitleNumber
      REMOVE IfcBuilding_ifc_type_name
      REMOVE IfcBuilding_SiteAddress.Country
      REMOVE IfcBuilding_SiteAddress.Purpose
      REMOVE IfcBuilding_RefElevation
      REMOVE IfcBuilding_SiteAddress.Region
      REMOVE IfcBuilding_BuildingAddress.Purpose
      REMOVE IfcBuilding_ShapeType
      REMOVE IfcBuilding_BuildingAddress.UserDefinedPurpose
      REMOVE IfcBuilding_SiteAddress.AddressLines
      REMOVE IfcBuilding_CompositionType
      REMOVE IfcBuilding_BuildingAddress.PostalCode
      REMOVE IfcBuilding_BuildingAddress.PostalBox
      REMOVE IfcBuilding_PredefinedType
      REMOVE IfcBuilding_ElevationOfRefHeight
      REMOVE IfcBuilding_BuildingAddress.AddressLines
      REMOVE IfcBuilding_Elevation
      REMOVE IfcBuilding_BuildingAddress.Town
      REMOVE IfcBuilding_SiteAddress.Town
      REMOVE IfcBuilding_OverallWidth
      REMOVE IfcBuilding_Phase
      REMOVE IfcBuilding_OverallHeight
      REMOVE IfcBuilding_SiteAddress.UserDefinedPurpose
      REMOVE IfcBuilding_ApplicableOccurrence
      REMOVE IfcBuilding_InteriorOrExteriorSpace
      REMOVE IfcBuilding_ElementType
      REMOVE IfcBuilding_ifc_type_object_id
      REMOVE IfcBuilding_SiteAddress.InternalLocation
      REMOVE IfcBuilding_SiteAddress.PostalBox
      REMOVE fme_feature_type
    -> IFC_Building (writer POSTGRES_3)
AttributeManager_5
    ATTR_TABLE:
      REMOVE IfcBuildingStorey_ifc_parent_unique_id
      REMOVE IfcBuildingStorey_ifc_unique_id
      REMOVE IfcBuildingStorey_Body
      REMOVE IfcBuildingStorey_Description
      REMOVE IfcBuildingStorey_ObjectType
      REMOVE IfcBuildingStorey_Tag
      REMOVE IfcBuildingStorey_Axis
      REMOVE IfcBuildingStorey_Box
      REMOVE IfcBuildingStorey_FootPrint
      REMOVE IfcBuildingStorey_SiteAddress.PostalCode
      REMOVE IfcBuildingStorey_LandTitleNumber
      REMOVE IfcBuildingStorey_SiteAddress.Description
      REMOVE IfcBuildingStorey_ifc_type_name
      REMOVE IfcBuildingStorey_SiteAddress.Country
      REMOVE IfcBuildingStorey_RefLongitude
      REMOVE IfcBuildingStorey_SiteAddress.Purpose
      REMOVE IfcBuildingStorey_RefElevation
      REMOVE IfcBuildingStorey_SiteAddress.Region
      REMOVE IfcBuildingStorey_BuildingAddress.Purpose
      REMOVE IfcBuildingStorey_ShapeType
      REMOVE IfcBuildingStorey_BuildingAddress.UserDefinedPurpose
      REMOVE IfcBuildingStorey_SiteAddress.AddressLines
      REMOVE IfcBuildingStorey_CompositionType
      REMOVE IfcBuildingStorey_BuildingAddress.PostalCode
      REMOVE IfcBuildingStorey_BuildingAddress.Country
      REMOVE IfcBuildingStorey_RefLatitude
      REMOVE IfcBuildingStorey_ElevationWithFlooring
      REMOVE IfcBuildingStorey_BuildingAddress.Region
      REMOVE IfcBuildingStorey_BuildingAddress.Description
      REMOVE IfcBuildingStorey_BuildingAddress.PostalBox
      REMOVE IfcBuildingStorey_PredefinedType
      REMOVE IfcBuildingStorey_ElevationOfRefHeight
      REMOVE IfcBuildingStorey_BuildingAddress.AddressLines
      REMOVE IfcBuildingStorey_BuildingAddress.Town
      REMOVE IfcBuildingStorey_SiteAddress.Town
      REMOVE IfcBuildingStorey_OverallWidth
      REMOVE IfcBuildingStorey_Phase
      REMOVE IfcBuildingStorey_OverallHeight
      REMOVE IfcBuildingStorey_SiteAddress.UserDefinedPurpose
      REMOVE IfcBuildingStorey_ApplicableOccurrence
      REMOVE IfcBuildingStorey_InteriorOrExteriorSpace
      REMOVE IfcBuildingStorey_ElementType
      REMOVE IfcBuildingStorey_ifc_type_object_id
      REMOVE IfcBuildingStorey_ElevationOfTerrain
      REMOVE IfcBuildingStorey_SiteAddress.InternalLocation
      REMOVE IfcBuildingStorey_BuildingAddress.InternalLocation
      REMOVE IfcBuildingStorey_SiteAddress.PostalBox
      REMOVE fme_feature_type
    -> IFC_BuildingStorey (writer POSTGRES_4)

Bookmark: Write to postGIS
IFC_Project (writer POSTGRES_1)
    attributes: GlobalID varchar(255), Name varchar(255), LongName varchar(255), ParentID varchar(255)
IFC_Site (writer POSTGRES_2)
    attributes: GlobalID varchar(255), Name varchar(255), LongName varchar(255), ParentID varchar(255), RefLatitude float8, RefLongtitude float8, RefElevation float8
IFC_Building (writer POSTGRES_3)
    attributes: GlobalID varchar(255), Name varchar(255), LongName varchar(255), ParentID varchar(255), ElevationOfTerrain float8
IFC_BuildingStorey (writer POSTGRES_4)
    attributes: GlobalID varchar(255), Name varchar(255), LongName varchar(255), ParentID varchar(255), Elevation float8

Bookmark: CSV
Note: CSV used for 3D affinement
CSV (reader CSV2_1)
    attributes: MoveX uint32, MoveY uint32, MozeZ uint8, Scale real32
    -> Affine_IFC [CSV]
    -> Affine_IFC_2 [CSV]

Bookmark: Write geometries to Postgis
FeatureWriter
    DATASET = $(PostgreSQL_CONNECTION)
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = $(PostgreSQL_CONNECTION)
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
FeatureWriter_2
    DATASET = $(PostgreSQL_CONNECTION)
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = $(PostgreSQL_CONNECTION)
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written

Bookmark: GeometryValidatorReport Excel
SpaceSummary (writer XLSXW_1)
    attributes: text string(200), txt_order string(200), sum string(200)
SpaceFailed (writer XLSXW_1)
    attributes: sum string(200), Basename string(50), Entity string(50), GlobalId string(22), Name string(20), Description string(20), LongName string(20), InteriorOrExteriorSpace string(20), MoveX string(200), MozeZ string(200), Scale string(200), MoveY string(200), count number(20), issue_found string(20), location_sample.x number(20), location_sample.y number(20), location_sample.z number(20), repair_state string(20), _element_index number(20)
SpaceRepaired (writer XLSXW_1)
    attributes: Basename string(50), Entity string(50), GlobalId string(22), issue_found string(20), repair_state string(20)
SpaceIssueSummary (writer XLSXW_1)
    attributes: status string(200), issue_found string(20), repair_state string(20), sum string(200), Basename string(50), Entity string(50)
BESummary (writer XLSXW_1)
    attributes: text string(200), txt_order string(200), sum string(200)
BESpaceFailed (writer XLSXW_1)
    attributes: sum string(200), Entity string(200), GlobalId string(200), Name string(200), Description string(200), LongName string(200), InteriorOrExteriorSpace string(200), Basename string(200), MoveX string(200), MozeZ string(200), Scale string(200), MoveY string(200), count number(20), issue_found string(20), location_sample.x number(20), location_sample.y number(20), location_sample.z number(20), repair_state string(20), _element_index number(20)
BERepaired (writer XLSXW_1)
    attributes: Entity string(200), GlobalId string(200), Basename string(200), issue_found string(20), repair_state string(20)
BESpaceIssueSummary (writer XLSXW_1)
    attributes: status string(200), issue_found string(20), repair_state string(20), sum string(200), Entity string(200), Basename string(200)

FME custom transformer ValidateGeometry

Parameters:
- BASENAME =
- ENTITY =
- GLOBALID =

Input (input)
    -> AttributeCreator
AttributeCreator
    ATTR_TABLE = SET_TO sum = 1
    -> Junction_4
Junction_4
    -> GeometryValidator
    -> GeometryRemover
    -> GeometryValidator_2
Failed_Geometries (output)
Note: OGC and other premises are validated seperately, so that it can be evaluated whether other issued can be repaired or not
Junction_5
    -> Junction_6
Note: GeometryValidator_2 : Failed
Junction_6
    -> ListExploder_2
ListExploder_2
    ATTR_ACCUM_MODE = Merge List Attributes
    ATTR_CONFLICT_RES = Use List Attribute Values
    INDEX_ATTR = _element_index
    LIST_ATTR = _issues{}
    ELEMENTS -> AttributeKeeper_3
AttributeKeeper_3
    CREATE_BULK_MODE_FEATURES = NO
    KEEP_ATTRS = GlobalId,issue_found,repair_state,Basename,Entity
    -> Junction_2
Note: Merge Valid Geometries
FeatureMerger
    ATTR_ACCUM_MODE = Merge Supplier
    ATTR_CONFLICT_RES = Use Requestor
    IGNORE_NULLS = No
    JOIN_KEYS = @Value(GlobalId) @Value(GlobalId) AUTO
    MERGE_TYPE = Attributes Only
    PROCESS_DUPS = NO
    REJECT_NULL_MISSING_KEYS = No
    SUPPLIERS_FIRST = No
    MERGED -> AttributeRemover
AttributeRemover
    REMOVE_ATTRS = _issues{0}.count,_issues{0}.issue_found,_issues{0}.location_sample.x,_issues{0}.location_sample.y,_issues{0}.location_sample.z,sum
    -> Valid_Geometries (output)
Valid_Geometries (output)
Note: Report all Failed features
ListExploder_3
    ATTR_ACCUM_MODE = Merge List Attributes
    ATTR_CONFLICT_RES = Use List Attribute Values
    INDEX_ATTR = _element_index
    LIST_ATTR = _issues{}
    ELEMENTS -> Report_Failed (output)
Report_Failed (output)
Junction_3
    -> Sorter
Sorter
    SORT_PARM = txt_order NATURAL ASCENDING
    SORTED -> Report_Summary (output)
Report_Summary (output)
ListExploder
    ATTR_ACCUM_MODE = Merge List Attributes
    ATTR_CONFLICT_RES = Use List Attribute Values
    INDEX_ATTR = _element_index
    LIST_ATTR = _issues{}
    ELEMENTS -> AttributeKeeper_2
    ELEMENTS -> AttributeCreator_9
AttributeKeeper_2
    CREATE_BULK_MODE_FEATURES = NO
    KEEP_ATTRS = GlobalId,issue_found,repair_state,Basename,Entity
    -> Junction_2
Note: Report Failed and repaired features
Junction_2
    -> Report_FailedRepaired (output)
Report_FailedRepaired (output)
AttributeCreator_9
    ATTR_TABLE = SET_TO status = repaired
    -> Aggregator_7
Aggregator_7
    ACCUM_ATTRS_NAME = Use Attributes From One Feature
    AGGREGATE_TYPE = Homogeneous Collection (If Possible)
    GROUP_BY = status fme_feature_type issue_found repair_state
    MODE = Geometry - Assemble One Level
    SEP = ,
    SUM = sum
    AGGREGATE -> AttributeKeeper_4
Note: Summarize Issues
AttributeKeeper_4
    CREATE_BULK_MODE_FEATURES = NO
    KEEP_ATTRS = status,sum,issue_found,repair_state,Basename,Entity
    -> Report_SummarizedIssues (output)
Report_SummarizedIssues (output)

Bookmark: Count all features
GeometryRemover
    -> Aggregator
Aggregator
    ACCUM_ATTRS_NAME = Drop Incoming Attributes
    MODE = Attributes Only
    SEP = ,
    SUM = sum
    AGGREGATE -> AttributeCreator_2
AttributeCreator_2
    ATTR_TABLE:
      SET_TO text = @Value(sum) features read
      SET_TO txt_order = 1
    -> Sorter

Bookmark: GeometryValidator
Note: Validate OGC
GeometryValidator_2
    ISSUE_ATTR_NAME = _issues
    PRESETS = Custom
    REPAIR = Yes
    RULES = OGC_VALID_CHECK OGC_VERSION]V1.2.0]FME_CONTROLLER_QUERY_FILE]transformers/dependencies/geometryvalidator8/OGC_VALID_CHECK.fme
    SUMMARY = Detailed
    PASSED -> GeometryRemover_5
    PASSED -> FeatureMerger [REQUESTOR]
    FAILED -> GeometryRemover_6
    FAILED -> Junction_5
    FAILED -> Failed_Geometries (output)
    REPAIRED -> FeatureMerger [REQUESTOR]
GeometryValidator
    ISSUE_ATTR_NAME = _issues
    PRESETS = Custom
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers/dependencies/geometryvalidator8/PLANAR_SURFACE.fme SELF_INTERSECTING CHECK_HOLE_TOUCHING_POLYGON]No]CONNECT_Z_MODE_SI]FIRST_WINS]SELF_INTERSECTION_TOLERANCE]None]FME_CONTROLLER_QUERY_FILE]transformers/dependencies/geometryvalidator8/SELF_INTERSECTING.fme SHELL_VALIDATION FLIP_APPEARANCE_MODE]FLIP_APPEARANCES]FME_CONTROLLER_QUERY_FILE]transformers/dependencies/geometryvalidator8/SHELL_VALIDATION.fme SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]0.0]FME_CONTROLLER_QUERY_FILE]transformers/dependencies/geometryvalidator8/TYPE_REPAIR.fme MISMATCHED_DIMENSIONS FORCE_DIMENSION]2D]FME_CONTROLLER_QUERY_FILE]transformers/dependencies/geometryvalidator8/MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers/dependencies/geometryvalidator8/MISSING_MEASURES_AND_ELEVATIONS.fme SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> GeometryRemover_2
    PASSED -> FeatureMerger [SUPPLIER]
    FAILED -> ListExploder
    FAILED -> GeometryRemover_3
    REPAIRED -> ListExploder
    REPAIRED -> GeometryRemover_4

Bookmark: Summarize Passed, Failed and Repaired Features
GeometryRemover_5
    -> Aggregator_5
Aggregator_5
    ACCUM_ATTRS_NAME = Drop Incoming Attributes
    MODE = Attributes Only
    SEP = ,
    SUM = sum
    AGGREGATE -> AttributeCreator_6
AttributeCreator_6
    ATTR_TABLE:
      SET_TO text = @Value(sum) features passed OGC
      SET_TO txt_order = 5
    -> Junction_3
GeometryRemover_6
    -> Aggregator_6
Aggregator_6
    ACCUM_ATTRS_NAME = Drop Incoming Attributes
    MODE = Attributes Only
    SEP = ,
    SUM = sum
    AGGREGATE -> AttributeCreator_7
AttributeCreator_7
    ATTR_TABLE:
      SET_TO text = @Value(sum) features failed OGC
      SET_TO txt_order = 6
    -> Junction_3
GeometryRemover_2
    -> Aggregator_2
Aggregator_2
    ACCUM_ATTRS_NAME = Drop Incoming Attributes
    MODE = Attributes Only
    SEP = ,
    SUM = sum
    AGGREGATE -> AttributeCreator_3
AttributeCreator_3
    ATTR_TABLE:
      SET_TO text = @Value(sum) features passed
      SET_TO txt_order = 2
    -> Junction_3
GeometryRemover_3
    -> Aggregator_3
    -> ListExploder_3
Aggregator_3
    ACCUM_ATTRS_NAME = Drop Incoming Attributes
    MODE = Attributes Only
    SEP = ,
    SUM = sum
    AGGREGATE -> AttributeCreator_4
AttributeCreator_4
    ATTR_TABLE:
      SET_TO text = @Value(sum) features failed
      SET_TO txt_order = 3
    -> Junction_3
GeometryRemover_4
    -> Aggregator_4
Aggregator_4
    ACCUM_ATTRS_NAME = Drop Incoming Attributes
    MODE = Attributes Only
    SEP = ,
    SUM = sum
    AGGREGATE -> AttributeCreator_5
AttributeCreator_5
    ATTR_TABLE:
      SET_TO text = @Value(sum) features repaired
      SET_TO txt_order = 4
    -> Junction_3
