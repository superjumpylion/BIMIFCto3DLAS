FME workspace 3_Intersection.fmw
Title: Intersection Reader
Description: Intersection Reader
This workspace reads the materialized view which calculated the 3D_Intersection, than calculates the volumes of these volumes. Volumes > 0 are written to a .ffs
Requirements
See the PostgreSQL dll to install the database.
Input
PostgreSQL_CONNECTION - Connection to the database
MATVIEW - Materialized view name
DestDataset_FFS - Location to store the .ffs dataset
History: 18 - 9 - 2021,Marjan Broekhuizen,Uploaded to Git

Parameters:
- DestDataset_FFS =
- MATVIEW =
- PostgreSQL_CONNECTION =

Writers:
- FFS_1: FFS to $(DestDataset_FFS)

Creator
    GEOMTYPE = Geometry Object
    NUM = 1
    CREATED -> FeatureReader [INITIATOR]
Note: Read intersection view
FeatureReader
    ATTRIBUTES = public.3dint_Westflank,"gid_1,gid_2,basename"
    ATTR_ACCUM_MODE = Only Use Result
    COMBINE_GEOM = Use Result
    DATASET = $(PostgreSQL_CONNECTION)
    FEATURETYPES = $(MATVIEW)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = $(PostgreSQL_CONNECTION)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> VolumeCalculator
Note: Calculate volume of intersection
VolumeCalculator
    MULT = 1
    SET_TRAIT = No
    VOLUME_ATTR = _volume
    -> Tester
Note: Test volume > 0
Tester
    BOOL_OP = OR
    COMPOSITE_TEST = 1
    TEST_CLAUSE = TEST @Value(_volume) > 0
    TEST_MODE = TEST
    PASSED -> Intersection (writer FFS_1)
Note: Resulting features represent overlap
Intersection (writer FFS_1)
    attributes: _volume real64
