FME workspace 4_FictiveLADMa.fmw
Title: Create LADM attributes
Description: Create LADM attributes
This workspace reads the LA_LegalSpaceBuildingUnit table from PostgreSQL and generates LADM attributes, which are stored to the PostgreSQL DBMS.
Requirements
See the PostgreSQL dll to install the database.
Input
PostgreSQL_CONNECTION - Connection to the database
History: 18 - 9 -2021,Marjan Broekhuizen,Uploaded to Git

Parameters:
- PostgreSQL_CONNECTION =

Readers:
- POSTGIS_1: POSTGIS from $(PostgreSQL_CONNECTION)

Writers:
- POSTGIS_2: POSTGIS to $(PostgreSQL_CONNECTION)

LA_LSBU (reader POSTGIS_1)
    attributes: basename varchar(200), entity varchar(200), globalid varchar(200), name varchar(200), description varchar(200), longname varchar(200), interiororexteriorspace varchar(200)
    -> Tester
Note: Not Pontsteiger, as Pontsteiger spaces can be grouped
Tester
    BOOL_OP = OR
    COMPOSITE_TEST = 1
    TEST_CLAUSE = TEST @Value(basename) = Pontsteiger
    TEST_MODE = TEST
    FAILED -> AttributeCreator
    FAILED -> GeometryRemover
AttributeCreator
    ATTR_TABLE:
      SET_TO Municipality = FME_CONDITIONAL:DEFAULT_VALUE'_FME_NO_OP_'BOOL_OP;OR;COMPOSITE_TEST;1;TEST @Value(basename) = IFC Schependomlaan'Amersfoort'BOOL_OP;OR;COMPOSITE_TEST;1;TEST @Value(basename) = 15-371 OA_Westflank 3BC_23-01-2019_Revspace'Utrecht'BOOL_OP;OR;COMPOSITE_TEST;1;TEST @Value(basename) = 7955_Library Rotterdam_Revspace'Rotterdam'FME_NUM_CONDITIONS4___
      SET_TO Indexnr = @Value(Municipality)A@Value(name)
    -> AttributeRemover
AttributeRemover
    REMOVE_ATTRS = Municipality
    -> GUIDGenerator
Note: Create LA_BU
GUIDGenerator
    -> AttributeRenamer
AttributeRenamer
    ATTR_TABLE = RENAME_SET_DEFAULT GFID > LA_BU
    MISSING_INPUT_ATTRS = REMOVE
    -> GeometryRemover_2
    -> LA_LSBU2 (writer POSTGIS_2)
LA_LSBU2 (writer POSTGIS_2)
    attributes: la_bu text, indexnr varchar(200), basename varchar(200), entity varchar(200), globalid varchar(200), name varchar(200), description varchar(200), longname varchar(200), interiororexteriorspace varchar(200)
GeometryRemover_2
    -> AttributeKeeper
AttributeKeeper
    CREATE_BULK_MODE_FEATURES = NO
    KEEP_ATTRS = basename,LA_BU
    -> GUIDGenerator_2
    -> LA_BU (writer POSTGIS_2)
LA_BU (writer POSTGIS_2)
    attributes: la_bu text, basename varchar(200)
Note: Create RRR_ID
GUIDGenerator_2
    -> AttributeRenamer_2
AttributeRenamer_2
    ATTR_TABLE = RENAME_SET_DEFAULT GFID > RRR_ID
    MISSING_INPUT_ATTRS = REMOVE
    -> RandomUserCreator
    -> LA_RRR (writer POSTGIS_2)
LA_RRR (writer POSTGIS_2)
    attributes: rrr_id text, la_bu text, basename varchar(200)
GeometryRemover
    -> AttributeCreator_2
Note: Create random name
RandomUserCreator
    gender = all
    nationaility = DE
    results = @Value(sum)
    -> AttributeCreator_3
AttributeCreator_3
    ATTR_TABLE = SET_TO Party = @Value(name.first) @Value(name.last)
    -> GUIDGenerator_3
Note: Create Party_ID
GUIDGenerator_3
    -> AttributeManager_2
AttributeManager_2
    ATTR_TABLE:
      RENAME_SET_VALUE Party > Name
      REMOVE name.first
      REMOVE name.last
      REMOVE gender
      REMOVE name.title
      REMOVE location.street
      REMOVE location.city
      REMOVE location.state
      REMOVE location.postcode
      REMOVE email
      REMOVE login.username
      REMOVE login.password
      REMOVE login.salt
      REMOVE login.md5
      REMOVE login.shal
      REMOVE login.sha256
      REMOVE dob
      REMOVE registered
      REMOVE phone
      REMOVE cell
      REMOVE picture.large
      REMOVE picture.medium
      REMOVE picture.thumbnail
      REMOVE nat
      REMOVE sum
      RENAME_SET_VALUE GFID > PARTY_ID
      REMOVE LA_BU
    -> LA_PARTY (writer POSTGIS_2)
LA_PARTY (writer POSTGIS_2)
    attributes: name varchar(200), party_id text, basename varchar(200), rrr_id text

Bookmark: Count features
AttributeCreator_2
    ATTR_TABLE = SET_TO sum = 1
    -> Aggregator
Aggregator
    ACCUM_ATTRS_NAME = Drop Incoming Attributes
    MODE = Attributes Only
    SEP = ,
    SUM = sum
    AGGREGATE -> RandomUserCreator
