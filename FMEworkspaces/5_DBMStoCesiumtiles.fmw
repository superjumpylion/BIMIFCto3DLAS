FME workspace 5_DBMStoCesiumtiles.fmw
Title: DBMS to Cesium tiles
Description: DBMS to Cesium tiles
This workspace is used to transform between DBMS and Cesium Tiles.
Requirements
See the PostgreSQL dll to install the database.
The database connection is removed for security reasons. Please add connectors between the read 'BuildingElements' and 'Cesium_view'
Input
PostgreSQL_CONNECTION - Connection to the database
DestTiles - Destionation of the tiles
History: 18 - 9 - 2021,Marjan Broekhuizen,Uploaded to Git

Parameters:
- DestDataset_CESIUM3DTILES =
- PostgreSQL_CONNECTION =

Writers:
- CESIUM3DTILES_1: CESIUM3DTILES to $(DestDataset_CESIUM3DTILES)

Bookmark: PostgreSQL DBMS
Creator
    GEOMTYPE = Geometry Object
    NUM = 1
    CREATED -> FeatureReader [INITIATOR]
Note: Read Space view and Building elements
FeatureReader
    ATTR_ACCUM_MODE = Only Use Result
    COMBINE_GEOM = Use Result
    DATASET = $(PostgreSQL_CONNECTION)
    FEATURETYPES = public.BuildingElements public.Cesium_view
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = $(PostgreSQL_CONNECTION)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes

Bookmark: Cesium Tilesets
tileset (writer CESIUM3DTILES_1)
tileset00 (writer CESIUM3DTILES_1)
