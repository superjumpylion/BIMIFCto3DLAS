FME workspace 1_IFCspaceAndGeoRefCheck.fmw
Title: IfcSpace and Georeference Check
Description: IfcSpace and Georeference Check
This workspace checks for IFC-files:
if it contains IfcSpace
its georeferencing capabilities
Requirements
This workspace utilized IfcGeoRefCheck, this can be downloaded from:
https://dd-bim.org/
Input
InputFolder - Folder which contains the to be validated IFC-file(s)
GEOREF - Path to IFCGeoRefChecked command executable
i.e. "C:\IfcGeoRefChecker_v3\IFCGeoRefCheckerCommand\bin\x64\Release\IFCGeoRefCheckerCommand.exe"
Output
A validation report (txt) in the input folder, with the results of the validation
Custom Transformers
IfcProjectCheck
IfcSpaceCheck
IfcGeoRef
History: 18 - 9 - 2021,Marjan Broekhuizen,Uploaded to Git

Parameters:
- GEOREF =
- InputFiles =
- InputFolder =

Writers:
- TEXTLINE_1: TEXTLINE to $(InputFolder)\validationreport.txt

Bookmark: 01. First Validations
Creator
    GEOMTYPE = Geometry Object
    NUM = 1
    CREATED -> IfcProjectCheck [FeatureReader_2_Initiator]
Note: Check if there are Ifc files in the folder, by checking if IfcProject exists
IfcProjectCheck
    InputFolder = $(InputFiles)
    -> IfcSpaceCheck
    LogOutput -> Junction_4
Note: Check if IfcSpace is present in (one of) the Ifc file(s)
IfcSpaceCheck
    InputFolder = $(InputFiles)
    -> IfcGeoRef
    LogOutput -> Junction_2
Note: Check Georeference values based on software IfcGeoRef. / Sends the outcoming log to the validation report, / Results JSON, which is not further used but could be used in future work. / IfcGeoRef should be installed, check private parameter GEOREF
IfcGeoRef
    GEOREF = $(GEOREF)
    InputFiles = $(InputFolder)\*.ifc
    InputFolder = $(InputFolder)
    LogOutput -> Sorter

Bookmark: Create Validation Report
Junction_2
    -> Sorter
Junction_4
    -> Sorter
Sorter
    SORT_PARM = txt_order NUMERIC ASCENDING
    SORTED -> text_line (writer TEXTLINE_1)
text_line (writer TEXTLINE_1)
    attributes: text_line_data buffer

FME custom transformer IfcGeoRef
Use IfcGeoRef to get Georef validation

Parameters:
- GEOREF =
- InputFiles =
- InputFolder =

Input (input)
    -> Sampler_2
Sampler_2
    RATE = 1
    SAMPLE_MODE = No
    SAMPLE_TYPE_LONG = First N Features
    SAMPLED -> FeatureReader_4 [INITIATOR]
FeatureReader_4
    ATTRIBUTES = IfcAnnotation,"GlobalId,Name,Description,ObjectType,fme_geometry{0},fme_geometry{1},fme_geometry{2},fme_geometry{3},fme_geometry{4},fme_geometry{5},fme_geometry{6},fme_geometry{7},fme_geometry{8},Annotation,Axis,Body,Box,FootPrint,fme_basename",IfcBeam,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename",IfcBuilding,"GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,fme_geometry{0},fme_geometry{1},fme_geometry{2},fme_geometry{3},fme_geometry{4},fme_geometry{5},fme_geometry{6},fme_geometry{7},fme_geometry{8},Annotation,Axis,Body,Box,FootPrint,fme_basename",IfcBuildingElementPart,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename",IfcBuildingElementProxy,"GlobalId,Name,Description,ObjectType,Tag,CompositionType,fme_geometry{0},fme_geometry{1},fme_geometry{2},fme_geometry{3},fme_geometry{4},fme_geometry{5},fme_geometry{6},fme_geometry{7},fme_geometry{8},Axis,Body,Box,FootPrint,fme_basename",IfcBuildingStorey,"GlobalId,Name,Description,ObjectType,LongName,CompositionType,Elevation,fme_geometry{0},fme_geometry{1},fme_geometry{2},fme_geometry{3},fme_geometry{4},fme_geometry{5},fme_geometry{6},fme_geometry{7},fme_geometry{8},Annotation,Axis,Body,Box,FootPrint,fme_basename",IfcColumn,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename",IfcCovering,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_basename",IfcDistributionElement,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename",IfcDoor,"GlobalId,Name,Description,ObjectType,Tag,OverallHeight,OverallWidth,PredefinedType,OperationType,UserDefinedOperationType,fme_geometry{0},fme_geometry{1},fme_geometry{2},fme_geometry{3},fme_geometry{4},fme_geometry{5},fme_geometry{6},fme_geometry{7},fme_geometry{8},Annotation,Axis,Body,Box,FootPrint,fme_basename",IfcFlowSegment,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename",IfcMember,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename",IfcOpeningElement,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename",IfcProject,"GlobalId,Name,Description,ObjectType,LongName,Phase,fme_geometry{0},fme_geometry{1},fme_geometry{2},fme_geometry{3},fme_geometry{4},fme_geometry{5},fme_geometry{6},fme_geometry{7},fme_geometry{8},Annotation,Axis,Body,Box,FootPrint,fme_basename",IfcRailing,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename",IfcSite,"GlobalId,Name,Description,ObjectType,LongName,CompositionType,RefLatitude,RefLongitude,RefElevation,LandTitleNumber,SiteAddress.Purpose,SiteAddress.Description,SiteAddress.UserDefinedPurpose,SiteAddress.InternalLocation,SiteAddress.AddressLines,SiteAddress.PostalBox,SiteAddress.Town,SiteAddress.Region,SiteAddress.PostalCode,SiteAddress.Country,fme_geometry{0},fme_geometry{1},fme_geometry{2},fme_geometry{3},fme_geometry{4},fme_geometry{5},fme_geometry{6},fme_geometry{7},fme_geometry{8},Annotation,Axis,Body,Box,FootPrint,fme_basename",IfcSlab,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename",IfcSpace,"GlobalId,Name,Description,ObjectType,LongName,CompositionType,PredefinedType,ElevationWithFlooring,fme_geometry{0},fme_geometry{1},fme_geometry{2},fme_geometry{3},fme_geometry{4},fme_geometry{5},fme_geometry{6},fme_geometry{7},fme_geometry{8},Annotation,Axis,Body,Box,FootPrint,fme_basename",IfcStair,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename",IfcTypeObject,"ifc_type_name,ifc_unique_id,GlobalId,Name,Description,ApplicableOccurrence,Tag,ElementType,PredefinedType,fme_basename",IfcVirtualElement,"GlobalId,Name,Description,ObjectType,Tag,fme_geometry{0},fme_geometry{1},fme_geometry{2},fme_geometry{3},fme_geometry{4},fme_geometry{5},fme_geometry{6},fme_geometry{7},fme_geometry{8},Annotation,Axis,Body,Box,FootPrint,fme_basename",IfcWall,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename",IfcWallStandardCase,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename",IfcWindow,"GlobalId,Name,Description,ObjectType,Tag,OverallHeight,OverallWidth,PredefinedType,PartitioningType,UserDefinedPartitioningType,fme_geometry{0},fme_geometry{1},fme_geometry{2},fme_geometry{3},fme_geometry{4},fme_geometry{5},fme_geometry{6},fme_geometry{7},fme_geometry{8},Annotation,Axis,Body,Box,FootPrint,fme_basename",PropertySetDefinition,fme_basename,QuantitySetDefinition,fme_basename
    ATTR_ACCUM_MODE = Only Use Result
    COMBINE_GEOM = Use Result
    DATASET = $(InputFiles)
    FEATURETYPES = IfcProject
    FORMAT = IFC
    IFC_ADD_PROJECTIONS = Yes
    IFC_CREATE_PQSET_DEFINITION_FEATURES = Yes
    IFC_EVALUATE_CSG_SOLIDS = No
    IFC_IFCSPACE_GEOMETRY = No
    IFC_IFC_EXPOSE_FORMAT_ATTRS = fme_basename,char(50)
    IFC_MERGE_TYPE_OBJECT_PQSETS = YES
    IFC_PQSET_READ_MODE = GEOMETRIES
    IFC_READER_MODE = Relational
    IFC_READER_VERSION = 2014
    IFC_READ_ALL_REPRESENTATIONS = YES
    IFC_SIMPLIFY_BASE_FACES = No
    IFC_SUBTRACT_OPENINGS = Yes
    IFC_TYPE_OBJECT_READ_MODE = MERGED
    IFC_USE_SEARCH_ENVELOPE = NO
    IFC_VERSION_OVERRIDE = auto-detect
    INTERACT = NONE
    OUTPUT_FEATURES_DISPLAY = Data Features
    IfcProject -> AttributeKeeper_2
AttributeKeeper_2
    CREATE_BULK_MODE_FEATURES = NO
    KEEP_ATTRS = fme_basename
    -> AttributeCreator_2
AttributeCreator_2
    ATTR_TABLE:
      SET_TO pathinput = $(InputFolder)\
      SET_TO spaceless_basename = @Value(fme_basename)
    -> StringReplacer
Note: Remove spaces for command line path reading
StringReplacer
    CASE = NO
    FIND_TEXT = " "
    NO_MATCH = _FME_NO_OP_
    REGEXP = NO
    SRC_ATTRS = spaceless_basename
    -> AttributeCreator
AttributeCreator
    ATTR_TABLE = SET_TO filenamepath =  @Value(pathinput)@Value(fme_basename).ifc
    -> JSONTemplater [ROOT]
JSONTemplater
    RESULT_ATTRIBUTE = _result
    ROOT_QUERY_EXPR:
      {
        "InputObjects":
        [
          {"fileName": fme:get-attribute("filenamepath")}
        ],
        "outputDirectory": fme:get-attribute("pathinput"),
        "outLog": true,
        "outJson": true
      }
    VISIBLE_QUERY_VALIDATE = Yes
    -> AttributeCreator_3
AttributeCreator_3
    ATTR_TABLE = SET_TO text_line_data = @Value(_result)
    -> AttributeCreator_4
    -> FeatureWriter [text_line]
AttributeCreator_4
    ATTR_TABLE = SET_TO command = $(GEOREF) @Value(pathinput)ifcgeoref@Value(spaceless_basename).json
    -> Aggregator
    -> 1On1_Merger_3 [Requestor]
Aggregator
    ACCUM_ATTRS_NAME = Merge Incoming Attributes
    CONCAT_ATTRS = command
    MODE = Attributes Only
    SEP = " && "
    AGGREGATE -> 1On1_Merger_2 [Requestor]
FeatureWriter
    DATASET = $(InputFolder)\ifcgeoref@Value(spaceless_basename).json
    DATASET_ATTR = _dataset
    FEATURE_TYPE_LIST_ATTR = _feature_types
    FORMAT = TEXTLINE
    GROUP_BY = fme_basename
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = application/json
    TEXTLINE_OVERWRITE_FILE = YES
    TEXTLINE_WRITE_LAST_EOL = YES
    TEXTLINE_WRITE_UTF8_BOM = YES
    TOTAL_FEATURES_WRITTEN_ATTR = _total_features_written
    SUMMARY -> Sampler
Sampler
    RATE = 1
    SAMPLE_MODE = No
    SAMPLE_TYPE_LONG = First N Features
    SAMPLED -> 1On1_Merger_2 [Supplier]
1On1_Merger_2
    Merged -> SystemCaller
SystemCaller
    CMD = @Value(command)
    -> 1On1_Merger_3 [Supplier]
1On1_Merger_3
    Merged -> AttributeKeeper_3
AttributeKeeper_3
    CREATE_BULK_MODE_FEATURES = NO
    KEEP_ATTRS = fme_basename,pathinput
    -> JSONExtractor
    -> FeatureReader [INITIATOR]
JSONExtractor
    EXTRACT_QUERY_TABLE = GeoRef10 json["LoGeoRef10"][*]["GeoRef10"] GeoRef20 json["LoGeoRef20"][*]["GeoRef20"] GeoRef30 json["LoGeoRef30"][*]["GeoRef30"] GeoRef40 json["LoGeoRef40"][*]["GeoRef40"] GeoRef50 json["LoGeoRef50"][*]["GeoRef50"]
    FILEPATH_OR_URL = @Value(pathinput)\IfcGeoRefChecker\CheckExport\@Value(fme_basename).json
    READ_FROM_FILE = YES
    EVALUATED -> JsonOutput (output)
JsonOutput (output)
FeatureReader
    ATTRIBUTES = text_line,"text_line_data,fme_geometry{0}"
    ATTR_ACCUM_MODE = Only Use Result
    COMBINE_GEOM = Use Result
    DATASET = @Value(pathinput)\IfcGeoRefChecker\CheckExport\@Value(fme_basename).txt
    FEATURETYPES = text_line
    FORMAT = TEXTLINE
    OUTPUT_FEATURES_DISPLAY = Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    text_line -> AttributeCreator_5
AttributeCreator_5
    ATTR_TABLE = SET_TO txt_order = 4
    -> LogOutput (output)
LogOutput (output)

FME custom transformer IfcSpaceCheck

Parameters:
- InputFolder =

Input (input)
    -> FeatureReader [INITIATOR]
Output (output)
LogOutput (output)

Bookmark: Check if IfcSpace is present
Note: Only read first 10 features to check if IfcSpace is present
Note: Note for multiple input files: It will not recognize when IfcSpace is present in one file, but not present in the other
FeatureReader
    ATTRIBUTES = IfcBeam,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcBuilding,"GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,fme_geometry{0},fme_geometry{1},fme_geometry{2},fme_geometry{3},fme_geometry{4},fme_geometry{5},fme_geometry{6},fme_geometry{7},fme_geometry{8},Axis,Body,Box,FootPrint,fme_basename,fme_dataset",IfcBuildingElementPart,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcBuildingElementProxy,"GlobalId,Name,Description,ObjectType,Tag,CompositionType,fme_geometry{0},fme_geometry{1},fme_geometry{2},fme_geometry{3},fme_geometry{4},fme_geometry{5},fme_geometry{6},fme_geometry{7},fme_geometry{8},Axis,Body,Box,FootPrint,fme_basename,fme_dataset",IfcBuildingStorey,"GlobalId,Name,Description,ObjectType,LongName,CompositionType,Elevation,fme_geometry{0},fme_geometry{1},fme_geometry{2},fme_geometry{3},fme_geometry{4},fme_geometry{5},fme_geometry{6},fme_geometry{7},fme_geometry{8},Axis,Body,Box,FootPrint,fme_basename,fme_dataset",IfcColumn,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcCovering,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_basename,fme_dataset",IfcDistributionElement,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcDoor,"GlobalId,Name,Description,ObjectType,Tag,OverallHeight,OverallWidth,fme_geometry{0},fme_geometry{1},fme_geometry{2},fme_geometry{3},fme_geometry{4},fme_geometry{5},fme_geometry{6},fme_geometry{7},fme_geometry{8},Axis,Body,Box,FootPrint,fme_basename,fme_dataset",IfcFlowSegment,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcMember,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcOpeningElement,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcProject,"GlobalId,Name,Description,ObjectType,LongName,Phase,fme_geometry{0},fme_geometry{1},fme_geometry{2},fme_geometry{3},fme_geometry{4},fme_geometry{5},fme_geometry{6},fme_geometry{7},fme_geometry{8},Axis,Body,Box,FootPrint,fme_basename,fme_dataset",IfcRailing,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_basename,fme_dataset",IfcSite,"GlobalId,Name,Description,ObjectType,LongName,CompositionType,RefLatitude,RefLongitude,RefElevation,LandTitleNumber,SiteAddress.Purpose,SiteAddress.Description,SiteAddress.UserDefinedPurpose,SiteAddress.InternalLocation,SiteAddress.AddressLines,SiteAddress.PostalBox,SiteAddress.Town,SiteAddress.Region,SiteAddress.PostalCode,SiteAddress.Country,fme_geometry{0},fme_geometry{1},fme_geometry{2},fme_geometry{3},fme_geometry{4},fme_geometry{5},fme_geometry{6},fme_geometry{7},fme_geometry{8},Axis,Body,Box,FootPrint,fme_basename,fme_dataset",IfcSlab,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_basename,fme_dataset",IfcSpace,"GlobalId,Name,Description,ObjectType,LongName,CompositionType,InteriorOrExteriorSpace,ElevationWithFlooring,fme_geometry{0},fme_geometry{1},fme_geometry{2},fme_geometry{3},fme_geometry{4},fme_geometry{5},fme_geometry{6},fme_geometry{7},fme_geometry{8},Axis,Body,Box,FootPrint,fme_basename,fme_dataset",IfcStair,"GlobalId,Name,Description,ObjectType,Tag,ShapeType,fme_geometry{0},fme_geometry{1},fme_geometry{2},fme_geometry{3},fme_geometry{4},fme_geometry{5},fme_geometry{6},fme_geometry{7},fme_geometry{8},Axis,Body,Box,FootPrint,fme_basename,fme_dataset",IfcTypeObject,"ifc_type_name,ifc_unique_id,GlobalId,Name,Description,ApplicableOccurrence,Tag,ElementType,PredefinedType,fme_basename,fme_dataset",IfcVirtualElement,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcWall,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcWallStandardCase,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcWindow,"GlobalId,Name,Description,ObjectType,Tag,OverallHeight,OverallWidth,fme_geometry{0},fme_geometry{1},fme_geometry{2},fme_geometry{3},fme_geometry{4},fme_geometry{5},fme_geometry{6},fme_geometry{7},fme_geometry{8},Axis,Body,Box,FootPrint,fme_basename,fme_dataset",PropertySetDefinition,"fme_basename,fme_dataset",QuantitySetDefinition,"fme_basename,fme_dataset"
    ATTR_ACCUM_MODE = Only Use Result
    COMBINE_GEOM = Use Result
    DATASET = $(InputFolder)
    FEATURETYPES = IfcSpace
    FORMAT = IFC
    IFC_ADD_PROJECTIONS = Yes
    IFC_CREATE_PQSET_DEFINITION_FEATURES = Yes
    IFC_EVALUATE_CSG_SOLIDS = No
    IFC_IFCSPACE_GEOMETRY = Yes
    IFC_IFC_EXPOSE_FORMAT_ATTRS = fme_basename,char(50) fme_dataset,char(50)
    IFC_MERGE_TYPE_OBJECT_PQSETS = YES
    IFC_PQSET_READ_MODE = GEOMETRIES
    IFC_READER_MODE = Relational
    IFC_READER_VERSION = 2014
    IFC_READ_ALL_REPRESENTATIONS = YES
    IFC_SIMPLIFY_BASE_FACES = No
    IFC_SUBTRACT_OPENINGS = Yes
    IFC_TYPE_OBJECT_READ_MODE = MERGED
    IFC_USE_SEARCH_ENVELOPE = NO
    IFC_VERSION_OVERRIDE = auto-detect
    INTERACT = NONE
    MAX_FEATURES = 10
    OUTPUT_FEATURES_DISPLAY = Data Features
    IfcSpace -> NoFeaturesTester
NoFeaturesTester
    NOINPUT -> AttributeCreator_2
    -> Sampler
Sampler
    RATE = 1
    SAMPLE_MODE = No
    SAMPLE_TYPE_LONG = First N Features
    SAMPLED -> Output (output)
    SAMPLED -> AttributeCreator_3
AttributeCreator_3
    ATTR_TABLE:
      SET_TO txt_order = 2
      SET_TO text_line_data = IfcSpace features are present
    -> Junction

Bookmark: New Bookmark
Note: error log
AttributeCreator_2
    ATTR_TABLE:
      SET_TO txt_order = 2
      SET_TO text_line_data = Error: Did not read IfcSpace, expected IfcSpace
    -> Junction
Note: Validation Report
Junction
    -> LogOutput (output)

FME custom transformer PostgresDeleteLoop
Check if fme_basename exists, if it does, delete it. if it does not, continue

Parameters:
- FME_BASENAME =

Input (input)
    -> Sampler_3
Sampler_3
    RATE = 1
    SAMPLE_MODE = No
    SAMPLE_TYPE_LONG = First N Features
    SAMPLED -> SQLExecutor [INITIATOR]
Note: Make list of fme_basename stored in PostGreSQL Validation table
SQLExecutor
    COMBINE_ATTRS = Result Attributes Only
    COMBINE_GEOM = Result Geometry Only
    DATASET = Validation01
    EXPOSED_ATTRIBUTE_LIST = fme_basename
    FORMAT = POSTGIS
    POSTGIS_NAMED_CONNECTION = Validation01
    SQL_STATEMENT = SELECT fme_basename FROM public."Validation" GROUP BY fme_basename
    RESULT -> FeatureMerger [REQUESTOR]
    INITIATOR -> FeatureMerger [SUPPLIER]
Note: If merged, fme_basename already exists, action: delete from Validation table where fme_basename exists, / if UnusedSupplier, fme_basename does not exist, action: continue translation
FeatureMerger
    ATTR_ACCUM_MODE = Merge Supplier
    ATTR_CONFLICT_RES = Use Requestor
    IGNORE_NULLS = No
    JOIN_KEYS = @Value(fme_basename) @Value(fme_basename) AUTO
    MERGE_TYPE = Attributes Only
    PROCESS_DUPS = NO
    REJECT_NULL_MISSING_KEYS = No
    SUPPLIERS_FIRST = No
    MERGED -> SQLExecutor_2 [INITIATOR]
    UNUSED_SUPPLIER -> Output (output)
Note: Delete from table where fme_basename = fme_basename
SQLExecutor_2
    COMBINE_ATTRS = Result Attributes Only
    COMBINE_GEOM = Result Geometry Only
    DATASET = Validation01
    EXPOSED_ATTRIBUTE_LIST = fme_basename
    FORMAT = POSTGIS
    POSTGIS_NAMED_CONNECTION = Validation01
    SQL_STATEMENT = DELETE FROM public."Validation" WHERE fme_basename = '@Value(fme_basename)'
    INITIATOR -> Input (output)
Input (output)
Output (output)

FME custom transformer IfcProjectCheck

Parameters:
- InputFolder =

FeatureReader_2_Initiator (input)
    -> FeatureReader_2 [INITIATOR]
Output (output)
LogOutput (output)

Bookmark: Create header for report
Note: Read IfcProject Properties
FeatureReader_2
    ATTRIBUTES = IfcAnnotation,"GlobalId,Name,Description,ObjectType,fme_geometry{0},fme_geometry{1},fme_geometry{2},fme_geometry{3},fme_geometry{4},fme_geometry{5},fme_geometry{6},fme_geometry{7},fme_geometry{8},Annotation,Axis,Body,Box,FootPrint,fme_basename,fme_dataset",IfcBeam,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename,fme_dataset",IfcBuilding,"GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,fme_geometry{0},fme_geometry{1},fme_geometry{2},fme_geometry{3},fme_geometry{4},fme_geometry{5},fme_geometry{6},fme_geometry{7},fme_geometry{8},Annotation,Axis,Body,Box,FootPrint,fme_basename,fme_dataset",IfcBuildingElementPart,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcBuildingElementProxy,"GlobalId,Name,Description,ObjectType,Tag,CompositionType,fme_geometry{0},fme_geometry{1},fme_geometry{2},fme_geometry{3},fme_geometry{4},fme_geometry{5},fme_geometry{6},fme_geometry{7},fme_geometry{8},Axis,Body,Box,FootPrint,fme_basename,fme_dataset",IfcBuildingStorey,"GlobalId,Name,Description,ObjectType,LongName,CompositionType,Elevation,fme_geometry{0},fme_geometry{1},fme_geometry{2},fme_geometry{3},fme_geometry{4},fme_geometry{5},fme_geometry{6},fme_geometry{7},fme_geometry{8},Annotation,Axis,Body,Box,FootPrint,fme_basename,fme_dataset",IfcColumn,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcCovering,"GlobalId,Name,Description,ObjectType,Tag,PredefinedType,fme_geometry{0},fme_geometry{1},fme_geometry{2},fme_geometry{3},fme_geometry{4},fme_geometry{5},fme_geometry{6},fme_geometry{7},fme_geometry{8},Axis,Body,Box,FootPrint,fme_basename,fme_dataset",IfcDistributionElement,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcDoor,"GlobalId,Name,Description,ObjectType,Tag,OverallHeight,OverallWidth,PredefinedType,OperationType,UserDefinedOperationType,fme_geometry{0},fme_geometry{1},fme_geometry{2},fme_geometry{3},fme_geometry{4},fme_geometry{5},fme_geometry{6},fme_geometry{7},fme_geometry{8},Annotation,Axis,Body,Box,FootPrint,fme_basename,fme_dataset",IfcFlowSegment,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcMember,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename,fme_dataset",IfcOpeningElement,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename,fme_dataset",IfcProject,"GlobalId,Name,Description,ObjectType,LongName,Phase,fme_geometry{0},fme_geometry{1},fme_geometry{2},fme_geometry{3},fme_geometry{4},fme_geometry{5},fme_geometry{6},fme_geometry{7},fme_geometry{8},Annotation,Axis,Body,Box,FootPrint,fme_basename,fme_dataset",IfcRailing,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename,fme_dataset",IfcSite,"GlobalId,Name,Description,ObjectType,LongName,CompositionType,RefLatitude,RefLongitude,RefElevation,LandTitleNumber,SiteAddress.Purpose,SiteAddress.Description,SiteAddress.UserDefinedPurpose,SiteAddress.InternalLocation,SiteAddress.AddressLines,SiteAddress.PostalBox,SiteAddress.Town,SiteAddress.Region,SiteAddress.PostalCode,SiteAddress.Country,fme_geometry{0},fme_geometry{1},fme_geometry{2},fme_geometry{3},fme_geometry{4},fme_geometry{5},fme_geometry{6},fme_geometry{7},fme_geometry{8},Annotation,Axis,Body,Box,FootPrint,fme_basename,fme_dataset",IfcSlab,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename,fme_dataset",IfcSpace,"GlobalId,Name,Description,ObjectType,LongName,CompositionType,PredefinedType,ElevationWithFlooring,fme_geometry{0},fme_geometry{1},fme_geometry{2},fme_geometry{3},fme_geometry{4},fme_geometry{5},fme_geometry{6},fme_geometry{7},fme_geometry{8},Annotation,Axis,Body,Box,FootPrint,fme_basename,fme_dataset",IfcStair,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename,fme_dataset",IfcTypeObject,"ifc_type_name,ifc_unique_id,GlobalId,Name,Description,ApplicableOccurrence,Tag,ElementType,PredefinedType,fme_basename,fme_dataset",IfcVirtualElement,"GlobalId,Name,Description,ObjectType,Tag,fme_geometry{0},fme_geometry{1},fme_geometry{2},fme_geometry{3},fme_geometry{4},fme_geometry{5},fme_geometry{6},fme_geometry{7},fme_geometry{8},Annotation,Axis,Body,Box,FootPrint,fme_basename,fme_dataset",IfcWall,"GlobalId,Name,Description,ObjectType,Tag,fme_geometry{0},fme_geometry{1},fme_geometry{2},fme_geometry{3},fme_geometry{4},fme_geometry{5},fme_geometry{6},fme_geometry{7},fme_geometry{8},Axis,Body,Box,FootPrint,fme_basename,fme_dataset",IfcWallStandardCase,"GlobalId,Name,Description,ObjectType,Tag,PredefinedType,fme_geometry{0},fme_geometry{1},fme_geometry{2},fme_geometry{3},fme_geometry{4},fme_geometry{5},fme_geometry{6},fme_geometry{7},fme_geometry{8},Annotation,Axis,Body,Box,FootPrint,fme_basename,fme_dataset",IfcWindow,"GlobalId,Name,Description,ObjectType,Tag,OverallHeight,OverallWidth,PredefinedType,PartitioningType,UserDefinedPartitioningType,fme_geometry{0},fme_geometry{1},fme_geometry{2},fme_geometry{3},fme_geometry{4},fme_geometry{5},fme_geometry{6},fme_geometry{7},fme_geometry{8},Annotation,Axis,Body,Box,FootPrint,fme_basename,fme_dataset",PropertySetDefinition,"fme_basename,fme_dataset",QuantitySetDefinition,"fme_basename,fme_dataset"
    ATTR_ACCUM_MODE = Only Use Result
    COMBINE_GEOM = Use Result
    DATASET = $(InputFolder)
    FEATURETYPES = IfcProject
    FORMAT = IFC
    IFC_ADD_PROJECTIONS = Yes
    IFC_CREATE_PQSET_DEFINITION_FEATURES = Yes
    IFC_EVALUATE_CSG_SOLIDS = No
    IFC_IFCSPACE_GEOMETRY = Yes
    IFC_IFC_EXPOSE_FORMAT_ATTRS = fme_basename,char(50) fme_dataset,char(50)
    IFC_MERGE_TYPE_OBJECT_PQSETS = YES
    IFC_PQSET_READ_MODE = GEOMETRIES
    IFC_READER_MODE = Relational
    IFC_READER_VERSION = 2014
    IFC_READ_ALL_REPRESENTATIONS = YES
    IFC_SIMPLIFY_BASE_FACES = No
    IFC_SUBTRACT_OPENINGS = Yes
    IFC_TYPE_OBJECT_READ_MODE = MERGED
    IFC_USE_SEARCH_ENVELOPE = NO
    IFC_VERSION_OVERRIDE = auto-detect
    INTERACT = NONE
    OUTPUT_FEATURES_DISPLAY = Data Features
    IfcProject -> FilenamePartExtractor_2
    IfcProject -> NoFeaturesTester_2
FilenamePartExtractor_2
    DIRNAME_ATTR = _dirname
    DIRPATH_ATTR = _dirpath
    EXTENSION_ATTR = _extension
    FULLNAME_ATTR = _filename
    ROOTNAME_ATTR = _rootname
    SRC_ATTR = @Value(fme_dataset)
    -> 1On1_Merger_2 [Requestor]
NoFeaturesTester_2
    NOINPUT -> AttributeCreator_2
    -> 1On1_Merger_2 [Supplier]
1On1_Merger_2
    Merged -> DateTimeStamper
DateTimeStamper
    DATETIME_ATTR = _timestamp
    INCLUDE_OFFSET = NO
    STAMP_TYPE = datetime
    TIMEZONE = utc
    -> AttributeCreator
AttributeCreator
    ATTR_TABLE:
      SET_TO text_line_data = Validation of @Value(fme_basename) in folder @Value(_dirname), datetime: @Value(_timestamp)
      SET_TO txt_order = 1
    -> Junction_3
    -> Sampler
Sampler
    RATE = 1
    SAMPLE_MODE = No
    SAMPLE_TYPE_LONG = First N Features
    SAMPLED -> Output (output)
Note: Validation Report
Junction_3
    -> LogOutput (output)
AttributeCreator_2
    ATTR_TABLE:
      SET_TO text_line_data = Error: No IfcProject found in $(InputFolder)
      SET_TO txt_order = 1
    -> LogOutput (output)

FME custom transformer 1On1_Merger
Merges features one on one, also used to hold translation until condition is reached

Requestor (input)
    -> FeatureMerger_2 [REQUESTOR]
Supplier (input)
    -> FeatureMerger_2 [SUPPLIER]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Merged (output)
Merged (output)
